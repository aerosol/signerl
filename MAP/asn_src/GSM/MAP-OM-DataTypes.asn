-- Pretty-printed by Asnp, the pretty-printer of France Telecom R&D (http://asn1.elibel.tm.fr/asnp/)
MAP-OM-DataTypes {itu-t identified-organization(4) etsi(0) mobileDomain(0)
  gsm-Network(1) modules(3) map-OM-DataTypes(12) version8(8)} DEFINITIONS
IMPLICIT TAGS ::=
BEGIN

EXPORTS
  ActivateTraceModeArg, ActivateTraceModeRes, DeactivateTraceModeArg,
    DeactivateTraceModeRes;

IMPORTS
  AddressString, IMSI
    FROM MAP-CommonDataTypes {itu-t identified-organization(4) etsi(0)
      mobileDomain(0) gsm-Network(1) modules(3) map-CommonDataTypes(18)
      version8(8)}
  ExtensionContainer
    FROM MAP-ExtensionDataTypes {itu-t identified-organization(4) etsi(0)
      mobileDomain(0) gsm-Network(1) modules(3) map-ExtensionDataTypes(21)
      version8(8)};

ActivateTraceModeArg ::= SEQUENCE {
  imsi                [0]  IMSI OPTIONAL,
  traceReference      [1]  TraceReference,
  traceType           [2]  TraceType,
  omc-Id              [3]  AddressString OPTIONAL,
  extensionContainer  [4]  ExtensionContainer OPTIONAL,
  ...}

TraceReference ::= OCTET STRING(SIZE (1..2))

TraceType ::= INTEGER(0..255)

-- Trace types are fully defined in TS GSM 12.08.
ActivateTraceModeRes ::= SEQUENCE {
  extensionContainer  [0]  ExtensionContainer OPTIONAL,
  ...}

DeactivateTraceModeArg ::= SEQUENCE {
  imsi                [0]  IMSI OPTIONAL,
  traceReference      [1]  TraceReference,
  extensionContainer  [2]  ExtensionContainer OPTIONAL,
  ...}

DeactivateTraceModeRes ::= SEQUENCE {
  extensionContainer  [0]  ExtensionContainer OPTIONAL,
  ...}

END
