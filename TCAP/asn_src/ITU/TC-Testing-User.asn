-- Module TC-Testing-User (Q.755.2:09/1997)
TC-Testing-User {itu-t recommendation q 755 modules(0) testing-user(1)
  version1(1)} DEFINITIONS ::=
BEGIN

IMPORTS
  --	OPERATION, 
  --	ERROR 
  --FROM TCAPMessages {itu-t recommendation q 773 modules(2) messages(1) version2(2)}
  --	APPLICATION-SERVICE-ELEMENT
  --FROM Notation-Extensions {joint-iso-itu-t remote-operations(4) notation-extension(2)}
  TMP-PDU
    FROM TC-TMP {itu-t recommendation q 755 modules(0) tmp(2) version1(1)}
  OPERATION-PACKAGE, Code, OPERATION, ERROR
    FROM Remote-Operations-Information-Objects {joint-iso-itu-t
      remote-operations(4) informationObjects(5) version1(0)};

-- application-context-names
ac-id OBJECT IDENTIFIER ::=
  {itu-t recommendation q 755 ac(5)}

testing-ac-id OBJECT IDENTIFIER ::= {ac-id testing-ac(1) version1(1)}

-- ase
testing-User-ASE OPERATION-PACKAGE ::= {
  CONSUMER INVOKES  {localConsumerOperation | globalConsumerOperation}
  -- consumer is the test system
  SUPPLIER INVOKES
    {class1SupplierOperation | class2SupplierOperation |
      class3SupplierOperation | class4SupplierOperation |
      globalSupplierOperation}
  -- supplier is the test responder
  ID                testing-ac-id
}

localConsumerOperation OPERATION ::= {
  ARGUMENT TMP-PDU RESULT TMP-PDU ERRORS  {localSupplierError}
  CODE                                    local:0
}

globalConsumerOperation OPERATION ::= {
  ARGUMENT TMP-PDU RESULT TMP-PDU ERRORS  {globalSupplierError}
  CODE
    global:{itu-t recommendation q 755 operations(1) consumer(1)}
}

class1SupplierOperation OPERATION ::= {
  ARGUMENT TMP-PDU RESULT TMP-PDU ERRORS  {localConsumerError}
  LINKED                                  {localConsumerOperation}
  CODE                                    local:1
}

class2SupplierOperation OPERATION ::= {
  ARGUMENT TMP-PDU ERRORS  {localConsumerError}
  LINKED                   {localConsumerOperation}
  CODE                     local:2
}

class3SupplierOperation OPERATION ::= {
  ARGUMENT TMP-PDU RESULT TMP-PDU CODE  local:3
}

class4SupplierOperation OPERATION ::= {ARGUMENT TMP-PDU CODE  local:4
}

globalSupplierOperation OPERATION ::= {
  ARGUMENT TMP-PDU RESULT TMP-PDU ERRORS  {globalConsumerError}
  LINKED                                  {globalConsumerOperation}
  CODE
    global:{itu-t recommendation q 755 operations(1) supplier(2)}
}

localConsumerError ERROR ::= {PARAMETER TMP-PDU CODE  local:1
}

globalConsumerError ERROR ::= {
  PARAMETER TMP-PDU CODE
    global:{itu-t recommendation q 755 errors(2) consumer(1)}
}

localSupplierError ERROR ::= {PARAMETER TMP-PDU CODE  local:2
}

globalSupplierError ERROR ::= {
  PARAMETER TMP-PDU CODE
    global:{itu-t recommendation q 755 errors(2) supplier(2)}
}

END
